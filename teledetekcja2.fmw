FME workspace teledetekcja2.fmw
Startup Python:
      import smtplib
      import fme
      from datetime import datetime

      gmail_user = fme.macroValues['email']
      gmail_password = fme.macroValues['password']
      to = fme.macroValues['clientEmail']

      current_time = datetime.now().strftime("%m/%d/%Y, %H:%M:%S")
      district = fme.macroValues['district']

      subject = 'Data processing started'
      body = 'Dear User,\n\ndata processing for district \"{}\" started on {} '.format(district, current_time)

      email_text = """\
      From: %s
      To: %s
      Subject: %s

      %s
      """ % (gmail_user, to, subject, body)

      try:
          server = smtplib.SMTP_SSL('smtp.gmail.com', 465)
          server.login(gmail_user, gmail_password)
          server.sendmail(gmail_user, to, email_text)
          server.quit()

          print('Email sent!')
      except:
          print('Something went wrong...')
Shutdown Python:
      import smtplib
      import fme
      import imghdr
      from email.message import EmailMessage

      gmail_user = fme.macroValues['email']
      gmail_password = fme.macroValues['password']
      to = fme.macroValues['clientEmail']

      time = round(fme.elapsedRunTime, 2)
      mean = round(fme.macroValues['mean'], 2)
      stdev = round(fme.macroValues['stdev'], 2)

      subject = 'Data processing finished'
      body = 'Session duration: {} \nMean: {} \nStandard Deviation: {}'.format(time, mean, stdev);


      newMessage = EmailMessage()
      newMessage['Subject'] = subject
      newMessage['From'] = gmail_user
      newMessage['To'] = to
      newMessage.set_content(body)

      with open("D:\\AGH\\SEMESTR_5\\bdp\\zad12\\ndvi_clipped\\ndvi.tif", 'rb') as f:
          image_data = f.read()
          image_type = imghdr.what(f.name)
          image_name = f.name.split("\\")[-1]

      newMessage.add_attachment(image_data, maintype='image', subtype=image_type, filename=image_name)


      try:
          with smtplib.SMTP_SSL('smtp.gmail.com', 465) as smtp:

              smtp.login(gmail_user, gmail_password)
              smtp.send_message(newMessage)

          print('Email sent!')
      except:
          print('Something went wrong...')

Parameters:
- DestDataset_TIFF =
- SourceDataset_JPEG2000 =
- SourceDataset_JPEG2000_3 =
- SourceDataset_SHAPEFILE =
- clientEmail =
- clouds =
- district =
- email =
- endDate =
- password =
- scihubPassword =
- scihubUser =
- startDate =

Readers:
- SHAPEFILE_1: SHAPEFILE from $(SourceDataset_SHAPEFILE)
- JPEG2000_1: JPEG2000 from $(SourceDataset_JPEG2000)
- JPEG2000_2: JPEG2000 from $(SourceDataset_JPEG2000_3)

Writers:
- TIFF_1: TIFF to $(DestDataset_TIFF) in UTM84-33N

T33UVV_20211227T102339_B04_10m (reader JPEG2000_1)
    -> RasterExpressionEvaluator [A]
T33UVV_20211227T102339_B08_10m (reader JPEG2000_2)
    -> RasterExpressionEvaluator [B]
RasterExpressionEvaluator
    EXPRESSION_LIST = AUTO (B[0]-A[0])/(B[0]+A[0])
    MODE = Two Rasters
    RESULT -> RasterExpressionEvaluator_2 [A]
RasterExpressionEvaluator_2
    EXPRESSION_LIST = UINT8 if(A[0]<=0,0,if(A[0]<=0.3,1,if(A[0]<=0.6,2,3)))
    MODE = One Raster
    RESULT -> AttributeCreator
AttributeCreator
    ATTR_TABLE:
      SET_TO _palette = RGB24
        0 0,0,64
        1 255,255,0
        2 0,255,0
        3 0,127,0
    -> RasterPaletteAdder
RasterPaletteAdder
    PALETTE_ATTR = _palette
    -> RasterStatisticsCalculator
RasterStatisticsCalculator
    RASTER_LEVEL = BAND_ONLY
    RASTER_STATS = "0   MEAN   STDEV  "
    -> Clipper [CLIPPEE]
Powiaty (reader SHAPEFILE_1)
    attributes: JPT_SJR_KO varchar(3), JPT_KOD_JE varchar(20), JPT_NAZWA_ varchar(128), JPT_ORGAN_ varchar(254), JPT_JOR_ID long, WERSJA_OD date, WERSJA_DO date, WAZNY_OD date, WAZNY_DO date, JPT_KOD__1 varchar(3), JPT_NAZWA1 varchar(3), JPT_ORGAN1 varchar(3), JPT_WAZNA_ varchar(3), ID_BUFORA_ double, ID_BUFORA1 double, ID_TECHNIC long, IIP_PRZEST varchar(20), IIP_IDENTY varchar(128), IIP_WERSJA varchar(32), JPT_KJ_IIP varchar(20), JPT_KJ_I_1 varchar(128), JPT_KJ_I_2 varchar(32), JPT_OPIS varchar(254), JPT_SPS_KO varchar(3), ID_BUFOR_1 long, JPT_ID long, JPT_KJ_I_3 varchar(3), Shape_Leng double, Shape_Area double
    -> Tester
Tester
    BOOL_OP = OR
    COMPOSITE_TEST = 1
    TEST_CLAUSE = CASE_INSENSITIVE_TEST @Value(JPT_NAZWA_) ENDS_WITH $(district)
    TEST_MODE = CASE_INSENSITIVE_TEST
    PASSED -> Reprojector_2
Reprojector_2
    DEST = UTM84-33N
    INTERPOLATION_TYPE_NAME = Nearest Neighbor
    RASTER_CELL_SIZE = Preserve Cells
    RASTER_TOLERANCE = 0.0
    REPROJECTED -> Clipper [CLIPPER]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> PythonCaller
PythonCaller
    PYTHONSOURCE:
      import fme
      import fmeobjects

      class FeatureProcessor(object):
          """Template Class Interface:
          When using this class, make sure its name is set as the value of the 'Class
          to Process Features' transformer parameter.
          """

          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              self.pyoutput(feature)


              FME_MacroValues['mean'] = feature.getAttribute('band0.mean')
              FME_MacroValues['stdev'] = feature.getAttribute('band0.stdev')

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> ndvi (writer TIFF_1)
ndvi (writer TIFF_1)
    attributes: _palette char(200), band0_mean float, band0_stdev float, _clipped char(3)
